-- This module provides a definition for two attributes thay may be
-- used to carry key attestation information within a
-- CertificationSigningRequest (aka PKCS10), or for other purposes.

-- IANA - Value needed
Attest-2023
    {iso(1) identified-organization(3) dod(6) internet(1) security(5)
    mechanisms(5) pkix(7) id-mod(0) id-mod-pkix-attest-01(TBDMOD) }
    
DEFINITIONS IMPLICIT TAGS ::=
BEGIN

IMPORTS


AlgorithmIdentifier{}, SIGNATURE-ALGORITHM, ALGORITHM,
ParamChoice
  FROM AlgorithmInformation-2009
      {iso(1) identified-organization(3) dod(6) internet(1) security(5)
      mechanisms(5) pkix(7) id-mod(0)
      id-mod-algorithmInformation-02(58)}

id-pkix, Certificate --, SingleAttribute if needed
FROM PKIX1Explicit-2009
      {iso(1) identified-organization(3) dod(6) internet(1)
      security(5) mechanisms(5) pkix(7) id-mod(0)
      id-mod-pkix1-explicit-02(51)}

Attribute, ATTRIBUTE,AttributeSet
FROM PKIX-CommonTypes-2009
    {iso(1) identified-organization(3) dod(6) internet(1) security(5)
     mechanisms(5) pkix(7) id-mod(0) id-mod-pkixCommon-02(57)}

id-aa
FROM SecureMimeMessageV3dot1
     { iso(1) member-body(2) us(840) rsadsi(113549)
        pkcs(1) pkcs-9(9) smime(16) modules(0) msg-v3dot1(21) } ;

-- Repeated here for easy reference.
--   id-aa OBJECT IDENTIFIER ::= {iso(1) member-body(2) usa(840)
--      rsadsi(113549) pkcs(1) pkcs-9(9) smime(16) attributes(2)}


-- IANA - Values needed
-- Branch for attestation statement types
id-ata OBJECT IDENTIFIER ::= { id-pkix (TBD1) }

-- A general comment is that a certificate is a signed binding between
-- public key and some identifying info. Below "cert" is an X.509
-- "Certificate". "opaqueCert" is just string of bytes that the
-- receiving CA must know how to parse given information not carried
-- in this object.  "typedCert" and "typedFlatCert" both use an OID to
-- identify their types, but differ in that the encoding for typedCert
-- is always valid ASN1, whereas the typedFlatCert is just a string of
-- bytes that must be interpreted according to the type.  Note that a
-- typedFlatCert MAY contain an encapsulated ASN1 object, but this is
-- not the best use of the type and is hereby discouraged.

CertificateChoice ::=
   CHOICE {
      cert Certificate, -- typical X.509 cert
--      opaqueCert [0] OCTET STRING, 
      typedCert  [1] TypedCert, 
      typedFlatCert [2] TypedFlatCert -- not ASN1 Parseable
   }

-- Cribbed from definition of CONTENT-TYPE
-- Alternately as TypedCert ::= SingleAttribute
--
TYPED-CERT ::= TYPE-IDENTIFIER -- object id and a matching ASN1
                               -- structure encoded as a sequence
CertType ::= TYPED-CERT.&id   

TypedCert ::= SEQUENCE {
              certType  TYPED-CERT.&id({TypedCertSet}),
              content   TYPED-CERT.&Type ({TypedCertSet}{@certType})
          }

TypedCertSet TYPED-CERT ::= {
             ... -- Empty for now, 
             }


-- The receiving entity is expected to be able to parse the certBody
-- field given the value of the certType field.  This differs from
-- TypedCert in that the contents of the certBody field are not
-- necessarily well formed ASN1 in this case the certType tells you
-- how to parse the body of the OCTET STRING,

TypedFlatCert ::= SEQUENCE {
    certType OBJECT IDENTIFIER,
    certBody OCTET STRING
}	


-- A sequence of certificates used to validate an attestation chain.
-- By convention, the first certificate in the chain is the one that
-- contains the public key used to verify the attestation.  If the
-- related attestStatementAttribute contains more than a single
-- attestation, this attribute is expected to contain all of the
-- certificates needed to validate all attestations

id-aa-attestChainCerts OBJECT IDENTIFIER ::= { id-aa (TBDAA1) }


attestCertCertsAttribute ATTRIBUTE ::= {
        TYPE SEQUENCE OF CertificateChoice
        COUNTS MAX 1
        IDENTIFIED BY id-aa-attestChainCerts
    }

-- If the signature is provided separately, the value field need not
-- contain the signature.  Note that some attestation methods include
-- a signature method in the part signed by the signature and some do
-- not.

ATTEST-STATEMENT ::= CLASS {
  &id                 OBJECT IDENTIFIER UNIQUE,
  &Type,                  -- NOT optional
  &algidPresent       ParamOptions DEFAULT absent,
  &sigPresent         ParamOptions DEFAULT absent,
  &SigType            DEFAULT OCTET STRING
  &ancillaryPresent   ParamOptions DEFAULT absent,
  &AncillaryType      DEFAULT OCTET STRING

} WITH SYNTAX {
  TYPE  &Type
  IDENTIFIED BY &id
  [ALGID IS &algidPresent]
  [SIGNATURE [TYPE &SigType] IS &sigPresent]
  [ANCILLARY [TYPE &AncillaryType] IS &ancillaryPresent]
}

AttestStatement { ATTEST-STATEMENT:IOSet}  ::= SEQUENCE
  {
    type          ATTEST-STATEMENT.&id({IOSet}),
    value         ATTEST-STATEMENT.&Type({IOSet}{@type}),
    algId         [0] AlgorithmIdentifier{SIGNATURE-ALGORITHM, {...}} OPTIONAL,
    signature [1] EXPLICIT ATTEST-STATEMENT.&SigType({IOSet}{@type}) OPTIONAL,
    ancillaryData [2] EXPLICIT ATTEST-STATEMENT.&AncillaryType({IOSet}{@type}) OPTIONAL
  }

-- An attribute that contains a attestation statement.

id-aa-attestStatement OBJECT IDENTIFIER ::= { id-aa (TBDAA2) }

attestAttribute ATTRIBUTE ::= {
        TYPE AttestStatement
        IDENTIFIED BY id-aa-attestStatement
    }

END
